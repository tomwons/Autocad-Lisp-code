;; Read CSV  -  Lee Mac
;; Parses a CSV file into a matrix list of cell values.
;; csv - [str] filename of CSV file to read
 
(defun LM:readcsv (csv / des lst sep str) 
  (if (setq des (open csv "r")) 
    (progn 
      (setq sep ",")
      (while (setq str (read-line des)) 
        (setq lst (cons (LM:csv->lst str sep 0) lst))
      )
      (close des)
    )
  )
  (reverse lst)
)

;; CSV -> List  -  Lee Mac
;; Parses a line from a CSV file into a list of cell values.
;; str - [str] string read from CSV file
;; sep - [str] CSV separator token
;; pos - [int] initial position index (always zero)
 
(defun LM:csv->lst (str sep pos / s) 
  (cond 
    ((not (setq pos (vl-string-search sep str pos)))
     (if (wcmatch str "\"*\"") 
       (list (LM:csv-replacequotes (substr str 2 (- (strlen str) 2))))
       (list str)
     )
    )
    ((or (wcmatch (setq s (substr str 1 pos)) "\"*[~\"]") 
         (and (wcmatch s "~*[~\"]*") (= 1 (logand 1 pos)))
     )
     (LM:csv->lst str sep (+ pos 2))
    )
    ((wcmatch s "\"*\"")
     (cons 
       (LM:csv-replacequotes (substr str 2 (- pos 2)))
       (LM:csv->lst (substr str (+ pos 2)) sep 0)
     )
    )
    ((cons s (LM:csv->lst (substr str (+ pos 2)) sep 0)))
  )
)

(defun LM:csv-replacequotes (str / pos) 
  (setq pos 0)
  (while (setq pos (vl-string-search "\"\"" str pos)) 
    (setq str (vl-string-subst "\"" "\"\"" str pos)
          pos (1+ pos)
    )
  )
  str
)

(defun pobierznazwe (csvname / data file) 
  (if 
    (and 
      (setq file (findfile csvname))
      (setq data (cdr (LM:readcsv file)))
    )
    (progn 
      (setq wanted_layer2 (mapcar '(lambda (e) (car e)) data))
      (princ 
        (strcat "(" 
                (apply 'strcat 
                       (mapcar '(lambda (e) (strcat "\"" e "\" ")) wanted_layer2)
                )
                ")"
        )
      )
    )
  )
  (princ)
)

(defun c:FASTPRINT (/ Listadruk lyt OldFda) 
  (vl-load-com)
  (pobierznazwe "listaszablon.csv")
  (setq Listadruk wanted_layer2)
  (setvar "FILEDIA" 0)
  (vlax-for lyt (vla-get-layouts (vla-get-activedocument (vlax-get-acad-object))) 
    (if (member (vla-get-name lyt) Listadruk) 
      (COMMAND "._-plot" "N" (vla-get-name lyt) "" "" "" "N" "T")
    )
  )
  (setvar "FILEDIA" 1)
  (princ)
)
