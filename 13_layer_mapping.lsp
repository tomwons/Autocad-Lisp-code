(defun c:hlsbreman () 
  (setq layerMappings '(("BH_Raumthermostat" . "SVP_Raumthermostat")
                        ("BS_Trinkwasser Warm" . "SVP_Trinkwasser Warm")
                        ("BS_Trinkwasser Warm_STEIGER" . "SVP_Trinkwasser Warm")
                        ("BS_Trinkwasser Kalt" . "SVP_Trinkwasser Kalt")
                        ("BS_Trinkwasser Kalt_STEIGER" . "SVP_Trinkwasser Kalt")
                        ("BS_Trinkwasser Zirkulation" . "SVP_Zirkulation")
                        ("BS_Trinkwasser Zirkulation_STEIGER" . "SVP_Zirkulation")
                        ("BH_Heizungsrücklauf" . "SVP_Heizungsrücklauf")
                        ("BH_Heizungsrücklauf_STEIGER" . "SVP_Heizungsrücklauf")
                        ("BH_Heizungsvorlauf" . "SVP_Heizungsvorlauf")
                        ("BH_Heizungsvorlauf_STEIGER" . "SVP_Heizungsvorlauf")
                        ("BL_Fortluft" . "SV_Exhaust")
                        ("BL_Außenluft" . "SV_Intake")
                        ("BL_Abluft" . "SV_Extract")
                        ("BL_Abluft-Text" . "SVP_Extract")
                        ("BL_Abluft Boden" . "SVP_Extract")
                        ("BL_Zuluft" . "SV_Supply")
                        ("BL_Zuluft Text" . "SVP_Supply")
                        ("BL_Zuluft Boden" . "SVP_Supply")
                        ("BL_Durchbrüche" . "SV_Durchbrüche")
                        ("BL_Durchbrüche-Text" . "SV_Durchbrüche-Text")
                        ; Dodaj inne warstwy i ich docelowe warstwy tutaj
                       )
  )

  (defun move-objects (fromLay toLay) 
    (setq ss (ssget "_X" (list (cons 8 fromLay))))
    (if ss 
      (repeat (sslength ss) 
        (setq objdata (entget (ssname ss 0))
              objdata (subst (cons 8 toLay) (cons 8 fromLay) objdata)
        )
        (entmod objdata)
        (ssdel (ssname ss 0) ss)
      )
    )
  )

  (foreach mapping layerMappings 
    (setq fromLay (car mapping)
          toLay   (cdr mapping)
    )
    (move-objects fromLay toLay)
  )
)
